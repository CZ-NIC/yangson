module tsig-algorithms {

  yang-version "1.1";

  namespace "http://www.nic.cz/ns/yang/tsig-algorithms";

  prefix "tsig";

  organization
    "CZ.NIC, z. s. p. o.";

  contact
    "Editor:   Ladislav Lhotka
               <mailto:lhotka@nic.cz>";

  description
    "This module translates IANA registry for TSIG Algorithm names to
     YANG identities.

     TSIG Algorithm names are text strings encoded using the syntax
     of a domain name. There is no structure required other than
     names for different algorithms must be unique when compared as
     DNS names, i.e., comparison is case insensitive. New algorithms
     are assigned using the IETF Consensus policy defined in RFC
     2434.";

  reference
    "IANA: Secret Key Transaction Authentication for DNS (TSIG)
     Algorithm Names.
     http://www.iana.org/assignments/tsig-algorithm-names/tsig-algorithm-names.xhtml";

  revision 2016-01-13 {
    description
      "Initial revision.";
    reference
      "TODO: put git tag here";
  }

  identity tsig-algorithm {
    description
      "Base identity from which specific TSIG Algorithms are
       derived.";
  }

  identity gss-tsig {
    base tsig-algorithm;
    description
      "GSS-TSIG algorithm. Optional to implement.";
    reference
      "RFC 3645: Generic Security Service Algorithm for Secret Key
       Transaction Authentication for DNS (GSS-TSIG).";
  }

  identity HMAC-MD5.SIG-ALG.REG.INT {
    base tsig-algorithm;
    description
      "Initial TSIG algorithm. Mandatory to implement.";
    reference
      "RFC 2845: Secret Key Transaction Authentication for DNS
       (TSIG).";
  }

  identity hmac-sha1 {
    base tsig-algorithm;
    description
      "hmac-sha1 algorithm. Mandatory to implement.";
    reference
      "RFC 4635: HMAC SHA TSIG Algorithm Identifiers.";
  }

  identity hmac-sha224 {
    base tsig-algorithm;
    description
      "hmac-sha224 algorithm. Optional to implement.";
    reference
      "RFC 4635: HMAC SHA TSIG Algorithm Identifiers.";
  }

  identity hmac-sha256 {
    base tsig-algorithm;
    description
      "hmac-sha256 algorithm. Mandatory to implement.";
    reference
      "RFC 4635: HMAC SHA TSIG Algorithm Identifiers.";
  }

  identity hmac-sha384 {
    base tsig-algorithm;
    description
      "hmac-sha384 algorithm. Optional to implement.";
    reference
      "RFC 4635: HMAC SHA TSIG Algorithm Identifiers.";
  }

  identity hmac-sha512 {
    base tsig-algorithm;
    description
      "hmac-sha512 algorithm. Optional to implement.";
    reference
      "RFC 4635: HMAC SHA TSIG Algorithm Identifiers.";
  }
}
