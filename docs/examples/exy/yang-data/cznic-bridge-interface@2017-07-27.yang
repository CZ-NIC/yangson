module cznic-bridge-interface {
  yang-version 1.1;
  namespace "http://www.nic.cz/ns/yang/bridge-interface";
  prefix brif;

  import ietf-interfaces {
    prefix if;
  }

  revision 2017-07-27 {
    description
      "Initial revision.";
  }

  // Identities

  identity bridge {
    base if:interface-type;
  }

  // Configuration data

  augment "/if:interfaces/if:interface" {
    when "derived-from-or-self(if:type, 'bridge')";
    leaf-list member-interface {
      type if:interface-ref;
    }
  }

  // State data

  augment "/if:interfaces-state/if:interface" {
    when "derived-from-or-self(if:type, 'bridge')";
    leaf-list member-interface {
      type if:interface-state-ref;
    }
  }
}
