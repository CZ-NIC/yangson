module example-3-a {

  yang-version 1.1;

  namespace "http://example.com/example-3/a";

  prefix ex3a;

  import ietf-yang-types {
    prefix yang;
  }

  include example-3-suba {
    revision-date 2017-08-01;
  }

  revision 2017-08-01;

  feature fea1;

  feature fea2;

  identity idX;

  grouping gbar {
    leaf bar {
      type string;
    }
  }

  container top {
    uses gquux;
    leaf foo {
      if-feature "fea1";
      type empty;
    }
  }
}
