module testb {

  yang-version "1.1";

  namespace "http://example.com/testb";

  prefix "tb";

  import defs {
    prefix "d";
  }

  import test {
    prefix "t";
  }

  revision 2016-04-26;

  identity CC-BY-SA {
    base t:share-alike;
    base t:all-uses;
  }

  augment "/t:contA" {
    choice choiB {
      mandatory "true";
      container contB {
        presence "YES";
        leaf leafC {
          type d:typA;
          mandatory "true";
        }
      }
      leaf leafI {
        type d:typB;
      }
      leaf leafN {
        if-feature "t:feA";
        type string;
      }
    }
    leaf leafR {
      type leafref {
	path "../t:listA/t:leafE";
      }
    }
    leaf leafS {
      type instance-identifier {
	require-instance true;
      }
    }
    leaf leafT {
      type identityref {
	base t:derivatives;
	base t:all-uses;
      }
    }
  }

  augment "/t:choiA" {
    leaf leafQ {
      type empty;
    }
  }

  rpc rpcA {
    input {
      leaf leafK {
        type d:typA;
      }
    }
    output {
      leaf-list llistC {
        type boolean;
        default "true";
        default "false";
      }
    }
  }

  notification noA {
    leaf leafO {
      type boolean;
      default "true";
    }
  }
}
