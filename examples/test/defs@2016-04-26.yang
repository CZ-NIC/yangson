module defs {

  yang-version "1.1";

  namespace "http://example.com/defs";

  prefix "d";

  revision 2016-04-26;

  typedef typA {
    type int16 {
      range "-6378..412";
    }
    default "11";
  }

  typedef typB {
    type typA {
      range "100..200";
    }
    default "111";
  }

  typedef typC {
    type enumeration {
      enum Mars {
        value "100";
      }
      enum Phobos;
      enum Deimos;
    }
  }

  typedef typD {
    type bits {
      bit un;
      bit dos;
      bit tres;
      bit cuatro;
    }
  }

  grouping grB {
    container contE {
      leaf leafJ {
        type empty;
      }
    }
  }
}
