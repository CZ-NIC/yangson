module defs {

  yang-version "1.1";

  namespace "http://example.com/defs";

  prefix "d";

  revision 2016-04-26;

  typedef typA {
    type int16 {
      range "-6378..412";
    }
    default "11";
  }

  typedef typB {
    type typA {
      range "100..200";
    }
    default "111";
  }

  typedef typC {
    type enumeration {
      enum Spades {
        value "100";
      }
      enum Hearts;
      enum Diamonds;
      enum Clubs;
    }
  }

  typedef typD {
    type bits {
      bit un;
      bit dos;
      bit tres;
      bit cuatro;
    }
  }

  typedef typE {
    type leafref {
      path "../../leafB";
    }
  }

  grouping grB {
    container contE {
      presence "explicit";
      leaf leafJ {
        type empty;
      }
      leaf leafU {
	type boolean;
	default true;
      }
    }
  }
}
