submodule subtest {

  yang-version "1.1";

  belongs-to test {
    prefix "t";
  }

  import ietf-inet-types {
    prefix "inet";
    revision-date 2013-07-15;
  }

  import ietf-inet-types {
    prefix "oin";
    revision-date 2010-09-24;
  }

  import defs {
    prefix "sd";
  }

  revision 2016-04-26;

  typedef typE {
    type sd:typA {
      range "-100..100";
    }
  }

  choice choiA {
    leaf-list llistB {
      type inet:ip-address-no-zone;
      min-elements "2";
      max-elements "3";
      ordered-by "user";
    }
    case caseA {
      container contC {
        leaf leafD {
          type sd:typB;
          default "199";
        }
        leaf-list llistA {
          type sd:typA;
          default "42";
          default "54";
        }
      }
      leaf leafH {
        type oin:ip-address;
	default "1.2.3.4";
      }
    }
    default "caseA";
  }
  leaf leafX {
    type inet:port-number;
    default 6378;
  }
}
