submodule impo-sub-a {
  yang-version 1.1;

  belongs-to test-import-complex {
    prefix impc;
  }

  revision 2026-04-01;

  feature sub-a-a;
  feature sub-a-b;

  identity impo-sub-a;

  identity cond-sub-a {
    if-feature sub-a-a;
  }
  identity cond-sub-b {
    if-feature sub-a-b;
  }

  typedef sub-type {
    type string {
      pattern "a+";
    }
  }
}
