submodule impo-sub-b {
  yang-version 1.1;

  belongs-to test-import-complex {
    prefix impc;
  }

  feature sub-b-a;
  feature sub-b-b;

  identity impo-sub-b;

  identity impo-cond-a {
    if-feature sub-b-a;
    base import-id;
  }
  identity impo-cond-b {
    if-feature sub-b-b;
    base import-id;
  }

  grouping sub-group {
    leaf a { type uint32; }
    leaf b { type uint32; }
  }
}
