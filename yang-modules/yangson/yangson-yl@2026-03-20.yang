module yangson-yl {
  yang-version 1.1;
  namespace "urn:yangson:xml:ns:yangson-yl";
  prefix yyl;

  import ietf-yang-library {
    prefix yanglib;
    revision-date 2016-06-21;
  }

  contact
    "Author: Ladislav Lhotka <ladislav@lhotka.name>";

  revision 2026-03-20 {
    description
      "Add flag 'keep-obsolete'.";
  }

  augment "/yanglib:modules-state/yanglib:module" {
    leaf keep-obsolete {
      type boolean;
      default "false";
      description
        "Setting the value of this leaf to true indicates that all
         schema nodes with obsolete status defined in this module and
         its submodules are kept in the schema and treated
         essentially as being current. If the value is false
         (default), obsolete schema nodes are omitted.

         In tree diagrams, schema nodes that have been un-obsoleted
         through this flag ale labeled with the 'O' (capital oh)
         character in the status field.";
    }
  }
}
