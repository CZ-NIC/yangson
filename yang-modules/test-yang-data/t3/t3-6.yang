module t3-6 {

  yang-version "1.1";

  namespace "http://example.com/t3-6";

  prefix "t";

  import ietf-restconf {
    prefix "rc";
    revision-date "2017-01-26";
  }

  revision 2025-07-01;

  rc:yang-data data {
    // "augment" statement is illegal as a substatement of ietf-restconf:yang-data statement
    augment "/system/login/message"  {
      leaf uid {
        type int16 {
          range "1000 .. 30000";
        }
      }
    }
  }

  container system {
    container login {
      leaf message {
        type string;
        description
          "Message given at start of login session.";
      }

      list user {
        key "name";
        leaf name {
          type string;
        }
        leaf full-name {
          type string;
        }
        leaf class {
          type string;
        }
      }
    }
  }
}
