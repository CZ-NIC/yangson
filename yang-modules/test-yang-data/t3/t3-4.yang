module t3-4 {

  yang-version "1.1";

  namespace "http://example.com/t3-4";

  prefix "t";

  import ietf-restconf {
    prefix "rc";
    revision-date "2017-01-26";
  }

  revision 2025-07-01;

  rc:yang-data data {
    container main {
      leaf a {
        type empty;
      }
    }

    // "typedef" statement is illegal as a substatement of ietf-restconf:yang-data statement
    typedef percent {
      type uint8 {
        range "0 .. 100";
      }
      description "Percentage";
    }
  }
}
