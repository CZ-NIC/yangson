module t2-4 {

  yang-version "1.1";

  namespace "http://example.com/t2-4";

  prefix "t";

  import ietf-restconf {
    prefix "rc";
    revision-date 2017-01-26;
  }

  revision 2025-07-01;

  rc:yang-data ydata {
    container data {
      // xpath reference outside context (we are locked inside ydata)
      when "/toplevel/leafA > 2";
    }
  }

  container toplevel {
    leaf leafA {
      type int32;
    }
  }
}
