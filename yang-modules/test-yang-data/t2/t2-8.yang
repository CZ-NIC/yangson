module t2-8 {

  yang-version "1.1";

  namespace "http://example.com/t3-9";

  prefix "t";

  import ietf-restconf {
    prefix "rc";
    revision-date 2017-01-26;
  }

  revision 2025-07-01;

  rc:yang-data ydata {
    container data {
      leaf ref {
        type leafref {
          // above toplevel /
          path "../../../data";
        }
      }
    }
  }
}
