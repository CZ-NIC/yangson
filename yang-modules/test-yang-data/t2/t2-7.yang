module t2-7 {

  yang-version "1.1";

  namespace "http://example.com/t2-7";

  prefix "t";

  import ietf-restconf {
    prefix "rc";
    revision-date 2017-01-26;
  }

  revision 2025-07-01;

  rc:yang-data ydata {
    container data {
      leaf ref {
        type leafref {
          // xpath reference outside context (we are locked inside ydata)
          path "../../toplevel/name";
        }
      }
    }
  }

  container toplevel {
    leaf name {
      type string;
    }

    leaf value {
      type int32;
    }
  }
}
