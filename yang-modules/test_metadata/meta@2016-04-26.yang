module meta {

  yang-version "1.1";

  namespace "http://example.com/meta";

  prefix "m";

  import ietf-yang-types {
    prefix "yang";
    revision-date 2013-07-15;
  }
  import ietf-yang-metadata {
    prefix "md";
  }

  revision 2016-04-26;

  md:annotation last-modified {
    type yang:date-and-time;
    description
      "This annotation contains the date and time when the
       annotated instance was last modified (or created).";
  }
}
